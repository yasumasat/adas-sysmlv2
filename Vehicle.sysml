//package Vehicle {
//	package Items {
//		item def VehicleDemension;	// 車両寸法
		/*
		enum def TurnSignal {		// 方向指示器
			off;
			right;
			left;
		}
*/
		/*
		enum def HazardLight {		// 非常点滅灯
			off;
			on;
		}
*/
//	}
//}
